module sysrepo-plugind {
  namespace "urn:sysrepo:plugind";
  prefix srpd;

  revision 2020-12-10 {
    description
      "Initial revision.";
  }

  container sysrepo-plugind {
    container plugin-order {
      description
        "The order in which to run plugins from the sysrepo-plugind.";
      leaf-list plugin {
        type string;
        ordered-by user;
        description
          "Plugin name.";
      }
    }
  }
}
